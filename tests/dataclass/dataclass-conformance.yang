module dataclass-conformance {
  yang-version 1.1;
  namespace "urn:dataclass-conformance";
  prefix dcc;

  // Fixtures for conformance details found by differential testing
  // against libyang: invert-match patterns, nested choices, RFC 7951
  // encoding strictness.

  leaf inverted {
    type string {
      pattern "x.*" {
        modifier invert-match;
      }
    }
  }

  container c {
    choice outer {
      case a {
        leaf marker { type string; }
        choice inner {
          mandatory true;
          case ia { leaf ia { type string; } }
          case ib { leaf ib { type string; } }
        }
      }
      case b { leaf ob { type string; } }
    }
  }

  leaf big { type uint64; }
  leaf e { type empty; }
  leaf flags { type bits { bit b1; bit b2; } }
  container pbox {
    presence "explicitly enabled";
    leaf setting { type string; }
  }

  leaf letters {
    type string {
      pattern '\p{L}+';
    }
  }

  leaf anchored {
    type string {
      // XSD regexes have no anchors: ^ and $ are literal characters
      pattern "a$b";
    }
  }

  leaf blob {
    type binary;
    default "eWFuZw==";
  }

  leaf target {
    type instance-identifier {
      require-instance false;
    }
  }

  list srv {
    key "name role";
    leaf name { type string; }
    leaf role { type string; }
  }
  list use {
    key "id";
    leaf id { type string; }
    leaf want-role { type string; }
    leaf pick {
      type leafref {
        path "../../srv[role=current()/../want-role]/name";
      }
    }
  }

  leaf u {
    type union {
      type decimal64 {
        fraction-digits 1;
        range "0.0..5.0";
      }
      type enumeration {
        enum off;
      }
    }
  }
  leaf ub {
    type union {
      type bits {
        bit x;
        bit y;
      }
      type uint8;
    }
  }
}
