module json-serialise {
  yang-version "1";
  namespace "http://rob.sh/yang/test/serialise/json";
  prefix "foo";
  organization "BugReports Inc";
  contact "A bug reporter";

  description
      "A test module";
  revision 2014-01-01 {
      description "april-fools";
      reference "fooled-you";
  }

  identity id-base {
    description
      "base identity";
  }

  identity idone {
    base id-base;
  }

  identity idtwo {
    base id-base;
  }

  typedef definedtype {
    type string;
  }

  typedef decimaldefinedtype {
    type decimal64 {
      fraction-digits 2;
    }
  }

  typedef decimalrangetype {
    type decimal64 {
      fraction-digits 10;
      range "1..max";
    }
  }

  typedef definedtypeunion {
    type union {
      type uint8;
      type string;
    }
  }

  typedef nhopenum {
    type enumeration {
      enum DROP {}
    }
  }

  typedef regexstring {
    type string {
      pattern '[0-9]+\.[0-9]+\.[0-9]+\.[0-9]+';
    }
  }

  typedef bits1 {
    type bits {
      bit flag1 {
	    position 1;
	  }
	  bit flag2 {
	    position 2;
	  }
	  bit flag3 {
	    position 3;
	  }
    }
  }

  container c1 {
    list l1 {
      key "k1";

      leaf k1 {
          type uint32;
      }

      leaf uint8 {
        type uint8;
      }

      leaf uint16 {
        type uint16;
      }

      leaf uint32 {
        type uint32;
      }

      leaf uint64 {
        type uint64;
      }

      leaf int8 {
        type int8;
      }

      leaf int16 {
        type int16;
      }

      leaf int32 {
        type int32;
      }

      leaf int64 {
        type int64;
      }

      leaf restricted-integer {
        type int8 {
          range "5..10";
        }
      }

      leaf string {
        type string;
      }

      leaf restricted-string {
        type string {
          pattern "a.*";
        }
      }

      leaf union {
        type union {
          type string;
          type uint32;
        }
      }

      leaf-list union-list {
        type union {
          type uint32;
          type string;
        }
      }

      leaf leafref {
        type leafref {
          path "/c1/t1/target";
        }
      }

      leaf binary {
        type binary;
      }

      leaf boolean {
        type boolean;
      }

      leaf decleaf {
        type decimal64 {
          fraction-digits 4;
        }
      }

      leaf enumeration {
        type enumeration {
          enum one;
          enum two;
        }
      }

      leaf identityref {
        type identityref {
          base id-base;
        }
      }

      leaf typedef-one {
        type definedtype;
      }

      leaf typedef-two {
        type definedtypeunion;
      }
      leaf typedef-three {
        type definedtypeunion;
      }

      leaf-list ll {
        type string;
      }

      leaf-list next-hop {
        type union {
          type regexstring;
          type nhopenum;
          type string;
          type bits1;
        }
      }

      leaf typedef-decimal {
        type decimaldefinedtype;
      }

      leaf range-decimal {
        type decimal64 {
          fraction-digits 10;
          range "1..10";
        }
      }

      leaf typedef-decimalrange {
        type decimalrangetype;
      }

      leaf bits {
        type bits {
	  bit flag1 {
	    position 1;
	  }
	  bit flag2 {
	    position 2;
	  }
	  bit flag3 {
	    position 3;
	  }
	}
      }

      choice test-choice {
        case one {
          leaf one-leaf {
            type string;
          }
        }
        case two {
          leaf two-leaf {
            type string;
          }
        }
      }
    }

    list l2 {
      key "k1";
      ordered-by user;

      leaf k1 {
       type uint32;
      }
    }

    list t1 {
      key "target";
      leaf target {
        type string;
      }
      leaf lol {
        default "lol";
        type string;
      }
      leaf bar {
        type string;
      }
    }
  }

  container two {
    leaf string-test {
      type string;
    }
  }

   list interface {
       key "name";
       leaf name {
         type string;
       }
       leaf admin-status {
         type boolean;
       }
       list address {
         key "ip";
         leaf ip {
           type string;
         }
       }
     }

     leaf mgmt-interface {
       type leafref {
         path "../interface/name";
       }
     }
}
