module dataclass {
  yang-version 1.1;
  namespace "http://pyangbind.example.com/dataclass";
  prefix "dc";

  description
    "Fixture for the pybind-dataclass output plugin. Deliberately places
     leaves WITH a YANG default before leaves WITHOUT one: since every
     generated field must carry some Python default (None, the YANG
     default, or a factory), this ordering must never provoke
     dataclasses' 'non-default argument follows default argument'
     TypeError -- neither within one class nor via inheritance from the
     generated base.";

  typedef percent {
    type uint8 {
      range "0..100";
    }
    default 50;
  }

  // A named enum typedef: used by >=2 leaves below, so it must be hoisted to
  // one module-level `type Direction = Literal[...]` alias (deduped).
  typedef direction {
    type enumeration {
      enum in;
      enum out;
    }
  }

  // identityref: aliased by its base identity name (Animal), covering every
  // derived identity in bare and module-prefixed spelling.
  identity animal;
  identity dog { base animal; }
  identity cat { base animal; }

  container box {
    leaf plain-before {
      type string;
    }
    leaf with-default {
      type string;
      default "lol";
    }
    leaf plain-after {
      type string;
    }
    leaf number-with-default {
      type uint16 {
        range "10..4096";
      }
      default 42;
    }
    leaf flag-with-default {
      type boolean;
      default true;
    }
    leaf from-typedef {
      type percent;
    }
    leaf-list strings-with-defaults {
      type string;
      default "one";
      default "two";
    }
    leaf bits-with-default {
      type bits {
        bit alpha;
        bit beta;
        bit gamma;
      }
      default "alpha gamma";
    }
    // Two leaves of the same named typedef -> one shared Direction alias.
    leaf dir-a {
      type direction;
    }
    leaf dir-b {
      type direction;
    }
    // identityref -> Animal alias.
    leaf pet {
      type identityref {
        base animal;
      }
    }
    // Inline anonymous enum -> stays inlined, NOT hoisted to a module alias.
    leaf mood {
      type enumeration {
        enum happy;
        enum sad;
      }
    }
    container nested-after-defaults {
      leaf inner-plain {
        type string;
      }
    }
    leaf plain-trailing {
      type string;
    }
  }

  // Structural-constraint material: list keys/unique/max-elements,
  // mandatory, leafref, choice/case, min-elements. Consumed by the
  // metadata table and the validate_tree() whole-tree pass.
  // Provenance material for --dataclass-origin-comments: a node pulled
  // in via `uses` and one via `augment`.
  grouping endpoint {
    leaf host {
      type string;
    }
  }

  container refs {
    uses endpoint;
    list server {
      key "name";
      unique "port";
      max-elements 4;
      leaf name {
        type string;
      }
      leaf port {
        type uint16;
      }
      leaf proto {
        type string;
        mandatory true;
      }
    }
    leaf active-server {
      type leafref {
        path "../server/name";
      }
    }
    leaf unchecked-server {
      type leafref {
        path "../server/name";
        require-instance false;
      }
    }
    leaf-list tags {
      type string;
      min-elements 1;
    }
    leaf ratio {
      type decimal64 {
        fraction-digits 2;
      }
    }
    // Serde-relevant encodings: 64-bit int (JSON string), binary
    // (base64), empty ([null]).
    leaf big {
      type uint64;
    }
    leaf blob {
      type binary;
    }
    leaf present {
      type empty;
    }
    choice transport {
      mandatory true;
      case tcp {
        leaf tcp-port {
          type uint16;
        }
      }
      case udp {
        leaf udp-port {
          type uint16;
        }
      }
    }
  }

  augment "/dc:refs" {
    leaf augmented-note {
      type string;
    }
  }
}
