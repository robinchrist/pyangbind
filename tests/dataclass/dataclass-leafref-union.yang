module dataclass-leafref-union {
  yang-version 1.1;
  namespace "urn:tests:dataclass-leafref-union";
  prefix dlu;

  import ietf-inet-types {
    prefix inet;
  }
  import dataclass-leafref-union-lists {
    prefix lists;
  }

  description
    "Fixture for leafref-as-union-member handling: pyang resolves
     i_leafref_ptr only for direct leafrefs, so union members must be
     resolved manually at codegen. Covers a string target, a non-string
     (uint16) target whose type must surface in the annotation and the
     assignment check, a leafref hidden behind a typedef, and a
     native-IP target (annotation, ip-union serde coercion).";

  typedef server-ref {
    type leafref {
      path "/dlu:server/dlu:name";
    }
  }

  list server {
    key "name";
    leaf name {
      type string;
    }
    leaf port {
      type uint16;
    }
    leaf address {
      type inet:ipv4-address-no-zone;
    }
  }

  leaf pick {
    type union {
      type leafref {
        path "../server/name";
      }
      type uint8;
    }
  }

  leaf pick-port {
    type union {
      type leafref {
        path "../server/port";
      }
      type enumeration {
        enum auto;
      }
    }
  }

  leaf pick-typedef {
    type union {
      type server-ref;
      type uint8;
    }
  }

  leaf pick-acl {
    // The frr-bgp-route-map comm-list-name shape: a union made up
    // ENTIRELY of leafrefs, each an absolute path into ANOTHER
    // module (resolved via the first step's prefix).
    type union {
      type leafref {
        path "/lists:acl/lists:name";
      }
      type leafref {
        path "/lists:acl6/lists:name";
      }
    }
  }

  leaf acl-direct {
    // Direct (non-union) cross-module leafref, for the
    // ignore-external-leafrefs escape hatch of validate_tree.
    type leafref {
      path "/lists:acl/lists:name";
    }
  }

  leaf pick-addr {
    type union {
      type leafref {
        path "../server/address";
      }
      type enumeration {
        enum any;
      }
    }
  }
}
